module snmpTemp1 {
  namespace "http://com/example/snmpTemp1";
  prefix snmpTemp1;

  import ietf-inet-types {
    prefix inet;
  }
  import tailf-ncs {
    prefix ncs;
  }
  import tailf-common {
    prefix tailf;
  }

  list snmpTemp1 {
    key comm-str;

    uses ncs:service-data;
    ncs:servicepoint "snmpTemp1";

    leaf comm-str {
      tailf:info "snmp-server community-string";
      type string;
    }

    // changed from leaf-list to leaf as we're only selecting one device for now
    leaf device {
      tailf:info "Pick any one IOS device";
      type leafref {
        path "/ncs:devices/ncs:device/ncs:name";
      }
    }

    // replace with your own stuff here
    leaf access {
      tailf:info "Specify ro or rw";
      type enumeration {
        enum ro;
        enum rw;
      }
    } // leaf access
  } // list snmpTemp1
}
